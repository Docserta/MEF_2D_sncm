Attribute VB_Name = "Declarations_publiques"
Option Explicit

'Fonction de récupération du username
Public Declare Function GetUserName Lib "advapi32.dll" Alias "GetUserNameA" (ByVal lpBuffer As String, nSize As Long) As Long

'Version de la macro
Public Const VMacro As String = "Version 0.3 du 20/04/17"
Public Const nMacro As String = "MEF_2D_Snecma"
Public Const nPath As String = "\\srvxsiordo\xLogs\01_CatiaMacros"
Public Const nFicLog As String = "logUtilMacro.txt"

Public Const Pi As Double = 3.1415926535

Public Langue As String

Public LgCarreau As Double
Public HtCarreau As Double

'Fichier de la nomenclature Catia
Public pubFicNomCatia As String
'Fichier des Cages Codes
Public Const FicCageCode As String = "C:\CFR\Dropbox\Macros\Nomenclature-Xto-SNECMA\STD121\Fournisseurs_Standard_Safran_Aircraft_Engines.csv"
'Séparateur des fichiers CSV
Public Const SepCSV As String = ";"

'Nombre de paramètres de base dans les nomenclatures (Qte, Reference, Révision, Definition, Nomenclature, source et product description)
'Les paramètre particuliers de l'environnement débute apres
Public Const NbColPrmStd As Integer = 7
'Nombre de paramètres non modifiables (Qte, Reference)
Public Const NbColPrmNomModif As Integer = 2

'Nom des champs de nomenclature (français/Anglais)
Public nQt As String
Public nRef As String
Public nRev As String
Public nDef As String
Public nNom As String
Public nDesc As String
Public nSrce As String

Public Type CoordXY
    X As Double
    Y As Double
End Type

'Variable de la barre de progression
Public pNbEt As Long
Public pEtape As Long
Public pItem As Long
Public pItems As Long

Public DimCadre As CoordXY 'Taille des carreau de localisation dans le plan
Public Std_Form As String 'Standard des formats de plans (Snecma, CFMI, Sylvercrest, Powerjet)

Public Function InitRegleH(Frmt As String) As c_Regles
'Initialise la règle horizontale de localisation des élements dans les plans
'No = Numéro du carreau
'Limit = limite supérieure du carreau en mm
'Frmt = format de plan (Snecma A0, CFMI E, Sylvercrest A0, Popwerjet A0)
Dim tRegle As c_Regle
Dim tRegles As c_Regles
Dim Marge As Double
Dim PremCarreau As Double
Dim AutreCarreau As Double
Dim LimPrecCarreau As Double
Dim NumCarreau As String
Dim i As Integer

    'Initialisation des valeurs
    Set tRegle = New c_Regle
    Set tRegles = New c_Regles
    Select Case Frmt
        Case "Snecma"
            Marge = 10
            PremCarreau = 130
            AutreCarreau = 130
        Case "CFMI"
            Marge = 13
            PremCarreau = 135.6
            AutreCarreau = 148.6
        Case " Sylvercrest"
            Marge = 10
            PremCarreau = 130
            AutreCarreau = 130
        Case "Powerjet"
            Marge = 10
            PremCarreau = 130
            AutreCarreau = 130
        Case Else
            MsgBox "erreur dans le choix du format des format de plans (Snecma, CFMI, Sylvercrest, Powerjet)", vbCritical, "Erreur de format"
            End
    End Select
    
    'Construction de la collection
    'La marge
    tRegle.No = 1
    tRegle.Limit = Marge
    tRegles.Add tRegle.No, tRegle.Limit
    'Le premier carreau
    tRegle.No = 2
    tRegle.Limit = Marge + PremCarreau
    tRegles.Add tRegle.No, tRegle.Limit
    LimPrecCarreau = tRegle.Limit
    
    'les carreau suivants
    For i = 3 To 10 'les carreaux vont de 1 à 9 maxi
        tRegle.No = i
        tRegle.Limit = LimPrecCarreau + AutreCarreau
        tRegles.Add tRegle.No, tRegle.Limit
        LimPrecCarreau = tRegle.Limit
    Next i
    Set InitRegleH = tRegles
    
    'Libération des classe
    Set tRegle = Nothing
    Set tRegles = Nothing
End Function

Public Function InitRegleV(Frmt As String) As c_Regles
'Initialise la règle horizontale de localisation des élements dans les plans
'En prenant en compte les lettres "interdites" (G,I,O,P,S,X,Y,Z)
'No = Numéro du carreau
'Limit = limite supérieure du carreau en mm
'Frmt = format de plan (Snecma A0, CFMI E, Sylvercrest A0, Popwerjet A0)
Dim tRegle As c_Regle
Dim tRegles As c_Regles
Dim Marge As Double
Dim PremCarreau As Double
Dim AutreCarreau As Double
Dim LimPrecCarreau As Double
Dim NumCarreau As String
Dim i As Integer
Dim lettres(9) As String

    'Initialisation des valeurs
    Set tRegle = New c_Regle
    Set tRegles = New c_Regles
    
    'Lettres communes
    For i = 1 To 9
        lettres(i) = Choose(i, "A", "B", "C", "D", "E", "F", "H", "J", "K")
    Next
    Select Case Frmt
        Case "Snecma"
            Marge = 10
            PremCarreau = 120
            AutreCarreau = 120
            lettres(7) = "G"
            lettres(8) = "H"
            lettres(9) = "J"
        Case "CFMI"
            Marge = 13
            PremCarreau = 92
            AutreCarreau = 105.1
        Case " Sylvercrest"
            Marge = 10
            PremCarreau = 120
            AutreCarreau = 120
        Case "Powerjet"
            Marge = 10
            PremCarreau = 120
            AutreCarreau = 120
        Case Else
            MsgBox "erreur dans le choix du format des format de plans (Snecma, CFMI, Sylvercrest, Powerjet)", vbCritical, "Erreur de format"
            End
    End Select
    
    'Construction de la collection
    'La marge
    tRegle.No = lettres(1)
    tRegle.Limit = Marge
    tRegles.Add tRegle.No, tRegle.Limit
    'Le premier carreau
    tRegle.No = lettres(2)
    tRegle.Limit = Marge + PremCarreau
    tRegles.Add tRegle.No, tRegle.Limit
    LimPrecCarreau = tRegle.Limit
    
    'les carreau suivants
    For i = 3 To 9 'les carreaux vont de 1 à 9 maxi
        tRegle.No = lettres(i)
        tRegle.Limit = LimPrecCarreau + AutreCarreau
        tRegles.Add tRegle.No, tRegle.Limit
        LimPrecCarreau = tRegle.Limit
    Next i
    Set InitRegleV = tRegles
    
    'Libération des classe
    Set tRegle = Nothing
    Set tRegles = Nothing
End Function

Attribute VB_Name = "ExportNom"
Option Explicit

' *****************************************************************
' * Export vers un fichier Excel de la nomenclature du Drawing actif
' * recupère la nomenclature brute générée par catia sur le product de référence
' * Collecte les labels et calcule leur position dans le plan
' * Collecte la liste des fournisseur et recupère les adresse dans un export SageX3
' * Création CFR le 23/03/17
' *
' *****************************************************************

Sub catmain()

Dim mdoc As Document
Dim oLigNomCatias As c_LNomCatias
Dim oLabels As c_Labels
Dim ofourns As c_CCodes
Dim oNomSnecmas As c_ItNomSnecmas
Dim oreglesH As c_Regles
Dim oreglesV As c_Regles

'Log de l'utilisation de la macro
LogUtilMacro nPath, nFicLog, nMacro, "ExportNom", VMacro

    'Check environnement
    'Test si un CatDrawing est actif
    If check_Env("Drawing") Then Set mdoc = CATIA.ActiveDocument
    'Configure les champs en fonction de la langue
    InitLanguage
    
    'Chargement du formulaire
    Load Frm_ExpNom
    Frm_ExpNom.Show
    'Bouton "annuler" choisi, on decharge le formulaire et on quite
    If Frm_ExpNom.CB_Annule Then
        Unload Frm_ExpNom
        Exit Sub
    End If
    'Stockage des infos du formulaire
    If Frm_ExpNom.Rbt_Sncm = True Then
        Std_Form = "Snecma"
    ElseIf Frm_ExpNom.Rbt_CFMI = True Then
        Std_Form = "CFMI"
    ElseIf Frm_ExpNom.Rbt_Sylver = True Then
        Std_Form = "Sylvercrest"
    ElseIf Frm_ExpNom.Rbt_Power = True Then
        Std_Form = "Powerjet"
    End If
    Unload Frm_ExpNom

    'Initialisation des variables
    Set oLigNomCatias = New c_LNomCatias
    Set oLabels = New c_Labels
    Set oNomSnecmas = New c_ItNomSnecmas
    Set oreglesH = InitRegleH(Std_Form)
    Set oreglesV = InitRegleV(Std_Form)
    
    'Collecte des Label
    Set oLabels = GetLabels(mdoc, oreglesH, oreglesV)

    'Collecte des adresses fournisseur
    Set ofourns = GetFourns
    
    'Construction de la classe des lignes de nomenclature catia
    Set oLigNomCatias = GetNomCatia(pubFicNomCatia)

    'Construction de la classe des lignes de nomenclature Snecma
    Set oNomSnecmas = GetNomSnecma(oLigNomCatias, oLabels)
    
    'Ajour des adresses fournisseurs
     AjoutFourn oNomSnecmas, ofourns

    'Export vers eXcel pour vérification
    exportXlNomSnecma oNomSnecmas

End Sub

Public Function GetNomCatia(cibleNomCatia As String) As c_LNomCatias
'Formate le fichier excel de la nomenclature généré par Catia
'Regoupe les ensembles
'Regroupe les détails

Dim objexcel
Dim objWBkNomCatia
Dim LigActive As Long
Dim ColActive As Integer
Dim NoLigFinNom As Long
Dim NoLigFinEns As Long
Dim NoLigDebDet As Long
Dim NoLigDebSSE As Long
Dim NomSSE As String
Dim cLigNomEn As c_LNomCatia
Dim cLigNomENs As c_LNomCatias
Dim cAttribut As c_Attribut
Dim cAttributs As c_Attributs
Dim cAttributEnv As c_Attribut
Dim cAttributEnvs As c_Attributs 'Collections des attributs de l'environnement (ex GSE)
Dim i As Long
Dim pEtape As Long, pNbEt As Long, pItem As Long, pItems As Long
Dim mbarre As c_ProgressBarre
Dim pos As Integer

'Initialisation des classes
    Set cAttributEnv = New c_Attribut
    Set cAttributEnvs = New c_Attributs
    Set cLigNomEn = New c_LNomCatia
    Set cLigNomENs = New c_LNomCatias
    
'Chargement de la barre de progression
    Set mbarre = New c_ProgressBarre
    mbarre.Titre = "Extraction des paramètres"
    mbarre.Progression = 1
    mbarre.Affiche
    pNbEt = 6: pEtape = 2: pItem = 1: pItems = 1

'Initialisation des objets Excel
    'Ouverture de la nom générée par Catia
    Set objexcel = CreateObject("EXCEL.APPLICATION")
    Set objWBkNomCatia = objexcel.Workbooks.Open(CStr(cibleNomCatia))
    objexcel.Visible = True

    'Recherche la position des lignes dans le fichier Excel
    NoLigFinNom = NoDerniereLigne(objWBkNomCatia)
    NoLigFinEns = NoDebRecap(objWBkNomCatia)
    NoLigDebDet = NoLigFinEns + 4
    NoLigDebSSE = 3
    
    'collecte de la liste des propriétés spécifiques à l'environnement (nom des attributs)
    LigActive = 4
    ColActive = NbColPrmStd + 1 'Première colonne après les attributs standards
    While objWBkNomCatia.ActiveSheet.cells(LigActive, ColActive).Value <> ""
        cAttributEnv.Nom = objWBkNomCatia.ActiveSheet.cells(LigActive, ColActive).Value
        cAttributEnv.Ordre = ColActive
        cAttributEnvs.Add cAttributEnv.Nom, cAttributEnv.Ordre
        ColActive = ColActive + 1
    Wend
           
    'Collecte des sous ensembles
    LigActive = 5

    'Creation de la liste des SSe (reference)
    pEtape = 3: pItem = 1: pItems = NoLigFinEns - LigActive
    While LigActive < NoLigFinEns
        mbarre.CalculProgression pEtape, pNbEt, pItem, pItems, "Création de la liste des sous ensembles"
        NomSSE = TestEstSSE(objWBkNomCatia.ActiveSheet.cells(LigActive, 1).Value)
        If NomSSE <> "False" Then
            cLigNomEn.ref = NomSSE
            'Ajout du sous ensemble a la collection
            cLigNomENs.Add cLigNomEn.ref
        End If
        LigActive = LigActive + 1
        pItem = pItem + 1
    Wend
    
'collecte des propriétés de chaque SSE
    LigActive = 5
    pEtape = 4: pItem = 1: pItems = NoLigFinEns - LigActive
    While LigActive < NoLigFinEns
        mbarre.CalculProgression pEtape, pNbEt, pItem, pItems, "collecte des propriétés de chaque sous ensemble"
        For Each cLigNomEn In cLigNomENs.Items
            If objWBkNomCatia.ActiveSheet.cells(LigActive, 2).Value = cLigNomEn.ref Then
                Set cAttributs = New c_Attributs
                Set cAttribut = New c_Attribut
                'Quantité
                pos = 1 'cAttributEnvs.Item(nQt).Ordre
                cLigNomEn.Qte = objWBkNomCatia.ActiveSheet.cells(LigActive, pos).Value
                ' Révision
                pos = 3 ' cAttributEnvs.Item(nRev).Ordre
                cLigNomEn.Rev = objWBkNomCatia.ActiveSheet.cells(LigActive, pos).Value
                ' Definition
                pos = 4 ' cAttributEnvs.Item(nDef).Ordre
                cLigNomEn.Def = objWBkNomCatia.ActiveSheet.cells(LigActive, pos).Value
                ' Nomenclature
                pos = 5 'cAttributEnvs.Item(nNom).Ordre
                cLigNomEn.Nom = objWBkNomCatia.ActiveSheet.cells(LigActive, pos).Value
                ' source
                pos = 6 'cAttributEnvs.Item(nSrce).Ordre
                cLigNomEn.Source = FormatSource(objWBkNomCatia.ActiveSheet.cells(LigActive, pos).Value)
                ' product description
                pos = 7 'cAttributEnvs.Item(nDesc).Ordre
                cLigNomEn.desc = objWBkNomCatia.ActiveSheet.cells(LigActive, pos).Value
                cLigNomEn.Comp = "E"
                'collecte des attributs liés a l'environnement
                For Each cAttributEnv In cAttributEnvs.Items
                    cAttribut.Nom = cAttributEnv.Nom
                    cAttribut.Ordre = cAttributEnv.Ordre
                    cAttribut.Valeur = objWBkNomCatia.ActiveSheet.cells(LigActive, cAttributEnv.Ordre).Value
                    cAttributs.Add cAttribut.Nom, cAttribut.Ordre, cAttribut.Valeur
                Next
                'Ajout de la collection des attributs a la ligne de nomenclature
                cLigNomEn.Attributs = cAttributs
                'vidage de la collection des attributs
                Set cAttribut = Nothing
            End If
        Next
        LigActive = LigActive + 1
        pItem = pItem + 1
    Wend
    Set cLigNomEn = Nothing
    
'Collecte des détails
    LigActive = NoLigDebDet + 1
    Set cLigNomEn = New c_LNomCatia
    pEtape = 5: pItem = 1: pItems = NoLigFinNom - LigActive
    While LigActive < NoLigFinNom
        mbarre.CalculProgression pEtape, pNbEt, pItem, pItems, "Collecte des propriétés des détails"
        Set cAttributs = New c_Attributs
        Set cAttribut = New c_Attribut
        'Collecte de la valeur des attributs Standards
        'Part Number
        cLigNomEn.ref = objWBkNomCatia.ActiveSheet.cells(LigActive, 2).Value
        ' Quantité
        cLigNomEn.Qte = objWBkNomCatia.ActiveSheet.cells(LigActive, 1).Value
        ' Révision
        cLigNomEn.Rev = objWBkNomCatia.ActiveSheet.cells(LigActive, 3).Value
        ' Definition
        cLigNomEn.Def = objWBkNomCatia.ActiveSheet.cells(LigActive, 4).Value
        ' Nomenclature
        cLigNomEn.Nom = objWBkNomCatia.ActiveSheet.cells(LigActive, 5).Value
        ' source
        cLigNomEn.Source = FormatSource(objWBkNomCatia.ActiveSheet.cells(LigActive, 6).Value)
        ' product description
        cLigNomEn.desc = objWBkNomCatia.ActiveSheet.cells(LigActive, 7).Value
        cLigNomEn.Comp = "D"
        'collecte de la valeur des attributs spécifiques a l'environnement
        For Each cAttributEnv In cAttributEnvs.Items
            cAttribut.Nom = cAttributEnv.Nom
            cAttribut.Ordre = cAttributEnv.Ordre
            cAttribut.Valeur = objWBkNomCatia.ActiveSheet.cells(LigActive, cAttributEnv.Ordre).Value
            cAttributs.Add cAttribut.Nom, cAttribut.Ordre, cAttribut.Valeur
        Next
        'Ajout de la collection des attributs a la ligne de nomenclature
        cLigNomEn.Attributs = cAttributs
        'vidage de la collection des attributs
        Set cAttribut = Nothing
        LigActive = LigActive + 1
        cLigNomENs.Add cLigNomEn.ref, cLigNomEn.Comp, cLigNomEn.Qte, cLigNomEn.Rev, cLigNomEn.Def, cLigNomEn.Nom, cLigNomEn.Source, cLigNomEn.desc, cLigNomEn.Attributs
        pItem = pItem + 1
    Wend

Set GetNomCatia = cLigNomENs

'Libération des classes
'Fermeture du fichier excel de nomenclature catia
    objWBkNomCatia.Close
Set cLigNomEn = Nothing
Set cLigNomENs = Nothing
Set cAttributEnv = Nothing
Set cAttributEnvs = Nothing
Set mbarre = Nothing

End Function

Private Sub AjoutFourn(ByRef oNomSnecmas, ByRef ofourns)
'Ajoute les adresses des fournisseur a la collection
Dim oFourn As c_CCode
Dim oNomSnecma As c_ItNomSnecma

    'Initialisation des classes
    Set oNomSnecma = New c_ItNomSnecma
    Set oFourn = New c_CCode

    'Pour chaque ligne de nomenclature on recherche le Fournisseur associé
    For Each oNomSnecma In oNomSnecmas.Items
        
        Set oFourn = SearchFirstFourn(oNomSnecma.desc, ofourns)
        If oFourn Is Nothing Then
        Else
            oNomSnecma.Fourn = Replace(oFourn.US, "$", Chr(10), 1, , vbTextCompare)
        End If
    Next
    
    'Libération des objets
    Set oNomSnecma = Nothing
    Set oFourn = Nothing

End Sub

Public Function GetNomSnecma(oLigNomCatias, oLabels) As c_ItNomSnecmas
'Récupération des attributs de la nomenclature Catia
'Association des labels aux item de la nomenclature
Dim olignom As c_LNomCatia
Dim oLabel As c_Label
Dim oNomSnecma As c_ItNomSnecma
Dim oNomSnecmas As c_ItNomSnecmas
Dim i As Long
Dim mbarre As c_ProgressBarre

    'Initialisation des classes
    Set oNomSnecma = New c_ItNomSnecma
    Set oNomSnecmas = New c_ItNomSnecmas
    Set olignom = New c_LNomCatia
    
    'Chargement de la barre de progression
    Set mbarre = New c_ProgressBarre
    mbarre.Affiche
    pNbEt = 6: pEtape = 5: pItem = 1: pItems = 1
    
    'Pour chaque ligne de nomenclature on recherche le label associé
    For Each olignom In oLigNomCatias.Items
        pItems = oLigNomCatias.Count
        mbarre.CalculProgression pEtape, pNbEt, pItem, pItems, "Génération de la nomenclature SNECMA"
        i = i + 1
        pItem = i
        Set oLabel = SearchFirstLbl(olignom.ref, oLabels)
        oNomSnecma.G03 = olignom.Qte
        oNomSnecma.Ident = olignom.Nom
        oNomSnecma.Rep = olignom.ref
        oNomSnecma.Fourn = olignom.desc
        'Le nom du fournisseur est enfouis dans la description on l'extraira plus tard
        oNomSnecma.Fourn = olignom.desc
        If oLabel Is Nothing Then
            oNomSnecma.desc = olignom.desc
        Else
            oNomSnecma.Det = listOfPlanche(olignom.ref, oLabels)
            oNomSnecma.Zone = oLabel.Position & "-" & oLabel.PL
            'Concaténation des désignation FR & EN
            oNomSnecma.desc = olignom.Attributs.Item("x_designation").Valeur
            oNomSnecma.desc = oNomSnecma.desc & Chr(10)
            oNomSnecma.desc = oNomSnecma.desc & olignom.Attributs.Item("x_designation anglais").Valeur
        End If
        oNomSnecmas.Add CStr(i), oNomSnecma.G03, oNomSnecma.G02, oNomSnecma.G01, oNomSnecma.Ident, oNomSnecma.CageCode, oNomSnecma.Det, oNomSnecma.Zone, oNomSnecma.Rep, oNomSnecma.desc, oNomSnecma.Fourn
        'RAZ de la ligne de nomsnecma
        Set oNomSnecma = New c_ItNomSnecma
    Next
    
    Set GetNomSnecma = oNomSnecmas

    'Liberation des classes
    Set oNomSnecma = Nothing
    Set oNomSnecmas = Nothing
    Set olignom = Nothing

End Function

Private Sub exportXlNomSnecma(oNomSnecmas)
'Export le contenu de la collection vers un fichier excel pour verification
Dim oXl
Dim oWBK
Dim lig As Long
Dim oNomSnecma As c_ItNomSnecma
    lig = 1
    Set oXl = CreateObject("EXCEL.APPLICATION")
    Set oWBK = oXl.Workbooks.Add
    oXl.Visible = True
    oWBK.ActiveSheet.cells(lig, "A").Value = "No ligne"
    oWBK.ActiveSheet.cells(lig, "B").Value = "G01"
    oWBK.ActiveSheet.cells(lig, "C").Value = "G02"
    oWBK.ActiveSheet.cells(lig, "D").Value = "G03"
    oWBK.ActiveSheet.cells(lig, "E").Value = "Ident"
    oWBK.ActiveSheet.cells(lig, "F").Value = "CageCode"
    oWBK.ActiveSheet.cells(lig, "G").Value = "Det"
    oWBK.ActiveSheet.cells(lig, "H").Value = "Zone"
    oWBK.ActiveSheet.cells(lig, "I").Value = "Rep"
    oWBK.ActiveSheet.cells(lig, "J").Value = "Description"
    oWBK.ActiveSheet.cells(lig, "K").Value = "Fournisseur"
    
    For lig = 1 To oNomSnecmas.Count
        Set oNomSnecma = oNomSnecmas.Item(lig)
        oWBK.ActiveSheet.cells(lig + 1, "A").Value = oNomSnecma.No
        oWBK.ActiveSheet.cells(lig + 1, "B").Value = oNomSnecma.G01
        oWBK.ActiveSheet.cells(lig + 1, "C").Value = oNomSnecma.G02
        oWBK.ActiveSheet.cells(lig + 1, "D").Value = oNomSnecma.G03
        oWBK.ActiveSheet.cells(lig + 1, "E").Value = oNomSnecma.Ident
        oWBK.ActiveSheet.cells(lig + 1, "F").Value = oNomSnecma.CageCode
        oWBK.ActiveSheet.cells(lig + 1, "G").Value = "'" & oNomSnecma.Det
        oWBK.ActiveSheet.cells(lig + 1, "H").Value = oNomSnecma.Zone
        oWBK.ActiveSheet.cells(lig + 1, "I").Value = oNomSnecma.Rep
        oWBK.ActiveSheet.cells(lig + 1, "J").Value = oNomSnecma.desc
        oWBK.ActiveSheet.cells(lig + 1, "K").Value = oNomSnecma.Fourn
    Next

'libération des classes
Set oNomSnecma = Nothing
Set oXl = Nothing
Set oWBK = Nothing

End Sub

Private Function SearchFirstLbl(ref As String, oLabels) As c_Label
'Recherche la première occurence du label dans la collection
Dim otemplab As c_Label
    Set otemplab = New c_Label
    For Each otemplab In oLabels.Items
        If otemplab.Rep = ref Then
            Set SearchFirstLbl = otemplab
            Exit For
        End If
    Next
End Function

Private Function SearchFirstFourn(desc As String, ofourns) As c_CCode
'Recherche la première occurence du fournisseur dans la collection
Dim oTempfour As c_CCode
    
    Set oTempfour = New c_CCode
    For Each oTempfour In ofourns.Items
        If oTempfour.Nom = desc Then
            Set SearchFirstFourn = oTempfour
            Exit For
        End If
    Next
    
End Function

Private Function listOfPlanche(ref As String, oLabels) As String
'collecte la liste des planches dans lesquelles apparait le repère
'ne renvois que les N° de planche a partir de la seconde
Dim otemplab As c_Label
Dim NbOcc As Integer
    listOfPlanche = ""
    Set otemplab = New c_Label
    For Each otemplab In oLabels.Items
        If otemplab.Rep = ref Then
            If NbOcc = 1 Then
                listOfPlanche = otemplab.PL
            ElseIf NbOcc > 1 Then
                listOfPlanche = listOfPlanche & "-" & otemplab.PL
            End If
            NbOcc = NbOcc + 1
        End If
    Next
End Function

Attribute VB_Name = "Fonctions"
Option Explicit

Public Function check_Env(Env As String) As Boolean
'Check si l'environnement est conforme aux prérequis de lancement des macros
'Env = "Part", "Product", "CatDrawing"
On Error Resume Next
Dim mPart As PartDocument
Dim mprod As ProductDocument
Dim mDraw As DrawingDocument
check_Env = False

Select Case UCase(Env)
    Case "PART" 'Test si un CatPart est actif
        Set mPart = CATIA.ActiveDocument
        If Err.Number <> 0 Then
            MsgBox "Activez un CATPart avant de lancer cette macro !", vbCritical, "Document actif incorrect"
            Err.Clear
            End
        Else
            check_Env = True
        End If
    Case "PRODUCT" 'Test si un CatProduct est actif
        Set mprod = CATIA.ActiveDocument
        If Err.Number <> 0 Then
            MsgBox "Activez un Catproduct avant de lancer cette macro !", vbCritical, "Document actif incorrect"
            Err.Clear
            End
        Else
            check_Env = True
        End If
    Case "DRAWING" 'Test si un CatDrawing est actif
        Set mDraw = CATIA.ActiveDocument
        If Err.Number <> 0 Then
            MsgBox "Activez un CatDrawing avant de lancer cette macro !", vbCritical, "Document actif incorrect"
            Err.Clear
            End
        Else
            check_Env = True
        End If
    End Select
    
    On Error GoTo 0
End Function

Public Function FormatScale(dScale As Double) As String
'renvoi l'echelle au format x/x
    Select Case dScale
        Case 0.1
            FormatScale = "1/10"
        Case 0.125
            FormatScale = "1/8"
        Case 0.2
            FormatScale = "1/5"
        Case 0.25
            FormatScale = "1/4"
        Case 0.5
            FormatScale = "1/2"
        Case 1
            FormatScale = "1/1"
        Case 2
            FormatScale = "2/1"
        Case 4
            FormatScale = "4/1"
        Case 5
            FormatScale = "5/1"
        Case 8
            FormatScale = "8/1"
        Case 10
            FormatScale = "10/1"
        Case 20
            FormatScale = "20/1"
        Case 50
            FormatScale = "50/1"
        Case 100
            FormatScale = "100/1"
    End Select
    
End Function

Public Function FormatSource(str As String) As String
'formate le contenu du champs source
'remplace "Inconu" ou "Unknown" par une chaine vide.
'remplace les codes champs sources par une string
FormatSource = str
Select Case str
    Case "Inconnu", "Unknown"
        FormatSource = ""
    Case "Bought", catProductBought
        FormatSource = "Acheté"
    Case "Made", catProductMade
        FormatSource = "Fabriqué"
End Select
End Function

Public Sub InitLanguage()
'Configure les champs en fonction de la langue
    Langue = Language
    If Langue = "EN" Then
        nQt = "Quantity"
        nRef = "Part Number"
        nRev = "Revision"
        nDef = "Definition"
        nNom = "Nomenclature"
        nDesc = "Product Description"
        nSrce = "Source"
    Else
        nQt = "Quantité"
        nRef = "Référence"
        nRev = "Révision"
        nDef = "Définition"
        nNom = "Nomenclature"
        nDesc = "Description du produit"
        nSrce = "Source"
    End If
End Sub

Public Function Language() As String
'Détecte la langue de l'interface Catia
'Ouvre un part vierge et test le nom du "Main Body"
Dim oFolder, ofs
Dim EmptyPartFolder, EmptyPartFile
Dim oEmptyPart  As PartDocument

On Error Resume Next
Set ofs = CreateObject("Scripting.FileSystemObject")
Set oFolder = ofs.GetFolder(CATIA.Parent.Path)
Set EmptyPartFolder = ofs.GetFolder(oFolder.ParentFolder.ParentFolder.Path & "\startup\templates") ' dossier relatif des modèles vides
Set EmptyPartFile = ofs.GetFile(EmptyPartFolder.Path & "\empty.CATPart")

If Err.Number = 0 Then
    On Error GoTo 0
    Set oEmptyPart = CATIA.Documents.Open(EmptyPartFile.Path)
    If oEmptyPart.Part.MainBody.Name = "PartBody" Then
        Language = "EN"
    Else
        Language = "FR"
    End If
End If

    oEmptyPart.Close
 Set oEmptyPart = Nothing
 Set EmptyPartFile = Nothing
 Set EmptyPartFolder = Nothing
 Set oFolder = Nothing
 Set ofs = Nothing
 On Error GoTo 0

End Function

'Public Function lecture_CSV() As c_CCodes
''Ouvre le fichier Csv et construit la collection des cages codes
'Dim oCCode As c_CCode
'Dim oCCodes As c_CCodes
'Dim Line_CSV As String
'Dim Idx As Long
'Dim fs, f
'
'    Set oCCode = New c_CCode
'    Set oCCodes = New c_CCodes
'    Idx = 1
'
'    Set fs = CreateObject("scripting.filesystemobject")
'    Set f = fs.opentextfile(FicCageCode, 1, 1)
'
'    Do While Not f.AtEndOfStream
'        Line_CSV = f.ReadLine
'        Set oCCode = SplitCSV(Line_CSV, Idx)
'        Idx = Idx + 1
'
'        oCCodes.Add oCCode.No, oCCode.Dom, oCCode.Nom, oCCode.EU, oCCode.US
'    Loop
'    f.Close
'
'    Set lecture_CSV = oCCodes
'    Set oCCode = Nothing
'    Set oCCodes = Nothing
'End Function

Public Function NoDebLstPieces(objWBk) As Long
'recherche la 1ere ligne des attributs des pièces
' la ligne commence par "Liste des pièces"
    Dim NomSeparateur As String
    Dim NoLigne As Long
    NoLigne = 1
    NomSeparateur = "Liste des pièces"
    While Left(objWBk.ActiveSheet.cells(NoLigne, 1).Value, Len(NomSeparateur)) <> NomSeparateur
        NoLigne = NoLigne + 1
    Wend
    NoDebLstPieces = NoLigne

End Function

Public Function NoDebRecap(objWBk As Variant) As Long
'recherche la 1ere ligne du récapitulatif des pièces
' la ligne commence par "Nomenclature de" ou "Recapitulation of:"
    Dim NomSeparateur As String
    Dim NoLigne As Integer
    NoLigne = 1
    If Langue = "EN" Then
        NomSeparateur = "Recapitulation of:"
    ElseIf Langue = "FR" Then
        NomSeparateur = "Récapitulatif sur"
    End If
    While Left(objWBk.ActiveSheet.cells(NoLigne, 1).Value, Len(NomSeparateur)) <> NomSeparateur
        NoLigne = NoLigne + 1
    Wend
    NoDebRecap = NoLigne
End Function

Public Function NoDerniereLigne(objWBk As Variant) As Long
'recherche la dernière ligne du fichier excel
'On part du principe que 2 lignes vide indiquent la fin du fichier
Dim NoLigne As Integer, NbLigVide As Integer
    NoLigne = 1
    NbLigVide = 0
    While NbLigVide < 2
        If objWBk.ActiveSheet.cells(NoLigne, 1).Value = "" Then
            NbLigVide = NbLigVide + 1
        Else
            NbLigVide = 0
        End If
    NoLigne = NoLigne + 1
    Wend
    NoDerniereLigne = NoLigne - 2
End Function

Public Function TestEstSSE(Ligne As String) As String
'test si la ligne correspond a une entète de sous ensemble
' la ligne commence par "Nomenclature de" ou "Bill of Material"
Dim NomSeparateur As String
Dim tmpNomSSE As String

    If Langue = "EN" Then
        NomSeparateur = "Bill of Material: "
    ElseIf Langue = "FR" Then
        NomSeparateur = "Nomenclature de "
    End If
    On Error Resume Next 'Test si la chaine est vide ou inférieur a len(nomséparateur)
    tmpNomSSE = Right(Ligne, Len(Ligne) - Len(NomSeparateur))
    If Err.Number <> 0 Then
         TestEstSSE = "False"
    Else
        If Left(Ligne, Len(NomSeparateur)) = NomSeparateur Then
            TestEstSSE = tmpNomSSE
        Else
            TestEstSSE = "False"
        End If
    End If
End Function

Public Function SplitCSV(str As String, Idx As Long) As Collection
'Extrait les valeurs de la chaine str séparées par le séparateur du fichier CSV (SepCSV)
Dim oVal As Collection

    Set oVal = New Collection

    Do While InStr(1, str, SepCSV, vbTextCompare) > 0
        oVal.Add Left(str, InStr(1, str, SepCSV, vbTextCompare) - 1)
        str = Right(str, Len(str) - InStr(1, str, SepCSV, vbTextCompare))
    Loop
    oVal.Add str
    Set SplitCSV = oVal
    
    'Libération des objets
    Set oVal = Nothing
End Function

'Private Function SplitCSV(str As String, Idx As Long) As c_CCode
''Extrait les valeurs de la chaine str séparées par le séparateur du fichier CSV (SepCSV)
'Dim oMember As c_CCode
'Dim oVal As Collection
'
'    Set oMember = New c_CCode
'    Set oVal = New Collection
'
'    Do While InStr(1, str, SepCSV, vbTextCompare) > 0
'        oVal.Add Left(str, InStr(1, str, SepCSV, vbTextCompare) - 1)
'        str = Right(str, Len(str) - InStr(1, str, SepCSV, vbTextCompare))
'    Loop
'    oVal.Add str
'    On Error Resume Next 'si oVal ne contient pas le nombre de valeurs
'
'    oMember.No = Idx
'    oMember.Dom = oVal.Item(1)
'    oMember.Nom = oVal.Item(2)
'    oMember.EU = oVal.Item(3)
'    oMember.US = oVal.Item(4)
'
'    On Error GoTo 0
'Set SplitCSV = oMember
'Set oVal = Nothing
'Set oMember = Nothing
'End Function

Public Sub LogUtilMacro(ByVal mPath As String, ByVal mFic As String, ByVal mMacro As String, ByVal mModule As String, ByVal mVersion As String)
'Log l'utilisation de la macro
'Ecrit une ligne dans un fichier de log sur le serveur
'mPath = localisation du fichier de log ("\\serveur\partage")
'mFic = Nom du fichier de log ("logUtilMacro.txt")
'mMacro = nom de la macro ("NomGSE")
'mVersion = Version de la macro ("version 9.1.4")
'mModule = Nom du module ("_Info_Outillage")

Dim mDate As String
Dim mUser As String
Dim nFicLog As String
Dim nLigLog As String
Const ForWriting = 2, ForAppending = 8

    mDate = Date & " " & Time()
    mUser = ReturnUserName()
    nFicLog = mPath & "\" & mFic

    nLigLog = mDate & ";" & mUser & ";" & mMacro & ";" & mModule & ";" & mVersion

    Dim fs, f
    Set fs = CreateObject("Scripting.FileSystemObject")
    On Error Resume Next
    Set f = fs.GetFile(nFicLog)
    If Err.Number <> 0 Then
        Set f = fs.opentextfile(nFicLog, ForWriting, 1)
    Else
        Set f = fs.opentextfile(nFicLog, ForAppending, 1)
    End If
    
    f.Writeline nLigLog
    f.Close
    On Error GoTo 0
    
End Sub

Private Function ReturnUserName() As String 'extrait d'un code de Paul, Dave Peterson Exelabo
'Renvoi le user name de l'utilisateur de la station
'fonctionne avec la fonction GetUserName dans l'entète de déclaration
    Dim Buffer As String * 256
    Dim BuffLen As Long
    BuffLen = 256
    If GetUserName(Buffer, BuffLen) Then _
    ReturnUserName = Left(Buffer, BuffLen - 1)
End Function

Public Function TestParamExist(mparams As Parameters, nParam As String) As String
'test si le paramètre passé en argument existe dans le part.
'si oui renvoi sa valeur,
'sinon la crée et lui affecte une chaine vide
Dim oParam As StrParam
On Error Resume Next
    Set oParam = mparams.Item(nParam)
If (Err.Number <> 0) Then
    ' Le paramètre n'existe pas, on le crée
    Err.Clear
    Set oParam = mparams.CreateString(nParam, "")
    oParam.Value = ""
End If
TestParamExist = oParam.Value
End Function

Attribute VB_Name = "Frm_ExpNom"
Attribute VB_Base = "0{5B553DB1-045E-43D6-996E-7A9C4F96180F}{30D5EE96-B883-4858-ABC1-2F21CCF34CA5}"
Attribute VB_GlobalNameSpace = False
Attribute VB_Creatable = False
Attribute VB_PredeclaredId = True
Attribute VB_Exposed = False
Attribute VB_TemplateDerived = False
Attribute VB_Customizable = False


Private Sub Btn_Navigateur_Click()
'Recupere le fichier de la nomenclature Catia
'Dim NomComplet As String

    'Ouverture du fichier de paramètres
    pubFicNomCatia = CATIA.FileSelectionBox("Selectionner le fichier de la nomenclature Catia", "*.xls", CatFileSelectionModeOpen)
    If pubFicNomCatia = "" Then Exit Sub 'on vérifie que qque chose a bien été selectionné

    Me.TBX_nNomCatia = pubFicNomCatia

End Sub

Private Sub BtnAnnul_Click()
    Me.CB_Annule = True
    Me.Hide
End Sub

Private Sub BtnOK_Click()
    Me.CB_Annule = False
    Me.Hide
End Sub


Private Sub UserForm_Initialize()
Me.Rbt_Sncm = True
End Sub

Attribute VB_Name = "Get_Fournisseurs"
Option Explicit

' *****************************************************************
' *
' * Ouvre le fichier Csv et construit la collection des cages codes
' * Création CFR le 10/02/2017
' * Dernière modification le :
' *****************************************************************

Public Function GetFourns() As c_CCodes

Dim oCCodes As c_CCodes
Dim oCCode As c_CCode
Dim Line_CSV As String
Dim Idx As Long
Dim fs, f
Dim oVal As Collection


    'Initialisation des variables
    Set oCCodes = New c_CCodes
    Set oCCode = New c_CCode
    Idx = 1
    Set fs = CreateObject("scripting.filesystemobject")
    Set f = fs.opentextfile(FicCageCode, 1, 1)

    Do While Not f.AtEndOfStream
        Set oVal = New Collection
        Line_CSV = f.ReadLine
        Set oVal = SplitCSV(Line_CSV, Idx)
        
        On Error Resume Next 'si oVal ne contient pas le nombre de valeurs

        oCCode.No = Idx
        oCCode.Dom = oVal.Item(1)
        oCCode.Nom = oVal.Item(2)
        oCCode.EU = oVal.Item(3)
        oCCode.US = oVal.Item(4)

        On Error GoTo 0
        
        Idx = Idx + 1
        oCCodes.Add oCCode.No, oCCode.Dom, oCCode.Nom, oCCode.EU, oCCode.US
    Loop
    f.Close

    Set GetFourns = oCCodes
    
    'Libération des oblets
    Set f = Nothing
    Set fs = Nothing
    Set oCCode = Nothing
    Set oCCodes = Nothing

End Function

Attribute VB_Name = "Get_Labels"
Option Explicit

' *****************************************************************
' * Construction de la collection des Labels
' * récupère les lablels sur toutes les planches et dans toutes les vues
' * calcul la position des label dans le quadrillage du plan
' * Création CFR le 27/03/17
' * modification le :
' *
' *
' *****************************************************************

Public Function GetLabels(mdoc, oregleH, oregleV) As c_Labels

Dim mSheets As DrawingSheets
Dim mSheet As DrawingSheet

Dim mviews As DrawingViews
Dim mview As DrawingView

Dim mTexts As DrawingTexts
Dim mText As DrawingText
Dim mLabel As DrawingText

Dim mLeads As DrawingLeaders
Dim mLead As DrawingLeader
Dim DimSheet As CoordXY 'Taille du calque
Dim PosView As CoordXY 'position de la vue dans le calque
Dim mbarre As c_ProgressBarre
Dim NbLbl As Long, cpt As Long
Dim NoPl As Integer 'numero de la planche dans l'odre de la collection des drawingSheets
Dim collabs As c_Labels
Dim LabEc As c_Label

'initialisation des variables
    Set mSheets = mdoc.Sheets
    Set collabs = New c_Labels

'Chargement de la barre de progression
    Set mbarre = New c_ProgressBarre
    mbarre.Titre = "Traitement des Labels"
    mbarre.Progression = 1
    mbarre.Affiche
    pNbEt = 6: pEtape = 1: pItem = 1: pItems = 1

    'Calcul du nombre de label pour barre de progression
    On Error Resume Next
    For Each mSheet In mSheets
        Set mviews = mSheet.Views
        If mviews.Count > 0 Then
            For Each mview In mviews
                Set mTexts = mview.Texts
                If mTexts.Count > 0 Then
                    For Each mText In mTexts
                        If InStr(1, CStr(mText.Name), "Numéro de pièce.") > 0 Then '"Numéro de pièce." ou "Balloon."
                            NbLbl = NbLbl + 1
                            mbarre.Balayage = NbLbl
                        End If
                    Next
                End If
            Next
        End If
    Next
    On Error GoTo 0
   
    For Each mSheet In mSheets 'Pour chaque planche
        NoPl = NoPl + 1
        'DimCadre = InitCadre(mSheet.PaperSize)
        Set mviews = mSheet.Views
        'Récupération de la longueur et de la hauteur du calque
        DimSheet.X = mSheet.GetPaperWidth
        DimSheet.Y = mSheet.GetPaperHeight
        If mviews.Count > 0 Then
            For Each mview In mviews 'Pour chaque vue
                Set mTexts = mview.Texts
                If mTexts.Count > 0 Then
                    For Each mText In mTexts 'Pour chaque texte
                        If InStr(1, CStr(mText.Name), "Numéro de pièce.") > 0 Then '"Numéro de pièce." ou "Balloon."
                            cpt = cpt + 1
                            Set LabEc = New c_Label
                            Set mLabel = mText
                            On Error Resume Next
                            Set mLeads = mLabel.Leaders
                            If Err.Number = 0 Then
                                mbarre.ProgressEtape (100 / NbLbl) * cpt, "Label : " & mText.Text
                                
                                LabEc.No = collabs.Count + 1
                                'LabEc.Rep = LabelRef(collabs, mTexts, mText, mview.Scale) 'si le repère est déjà présent dans la collection on ajoute "REF"
                                '#test suppression zero non significatifs
                                If IsNumeric(mText.Text) Then
                                    LabEc.Rep = CInt(mText.Text)
                                End If
                                'LabEc.Rep = mText.Text
                                LabEc.PL = NoPl
                                'LabEc.Position = PosLbl(mLabel, mview, DimCadre, DimSheet)
                                LabEc.Position = PosLbl(mLabel, mview, oregleH, oregleV, DimSheet)
                                LabEc.RefView = mview.Name
                                'Vérifie les fleches du label
                                For Each mLead In mLeads
                                    HeadLead mLead
                                Next
                                collabs.Add LabEc.No, LabEc.Rep, LabEc.PL, LabEc.Position, LabEc.RefView
                            Else
                                Err.Clear
                                On Error GoTo 0
                            End If
                        ElseIf InStr(1, CStr(mText.Name), "Numéro de pièce.") > 0 Then '"Numéro de pièce." ou "Balloon." Then
                        
                        End If
                    Next
                End If
             Next
        End If
    Next
    
'Export vers eXcel pour vérification
exportXlLbl collabs
Set GetLabels = collabs

'Libération des classes
Set collabs = Nothing
Set LabEc = Nothing
Set mbarre = Nothing

End Function

Private Sub HeadLead(mLead)
'Change la flèche du Label si elle n'est pas conforme au standard
'la flèche doit être de type catFilledCircle () si elle ne pointe pas sur une arrète
    If mLead.HeadSymbol <> 14 Then
        mLead.HeadSymbol = catFilledCircle
    End If
End Sub

Private Function LabelRef(collabs, mTexts, mText As DrawingText, ech As Double) As String
'si le repère est déjà présent dans la collection on ajoute "REF"
Dim olab As c_Label
Dim TxtRef As DrawingText
Dim DecalRef As CoordXY

    DecalRef.X = AnchorLbl(mText).X / ech
    DecalRef.Y = AnchorLbl(mText).Y / ech
    Set olab = New c_Label
    On Error Resume Next
    If collabs.Count = 0 Then
        LabelRef = mText.Text
    Else
        For Each olab In collabs.Items
            If IsNumeric(mText.Text) Then
                If olab.Rep = mText.Text Then
                    LabelRef = mText.Text & "REF"
                    'Set TxtRef = mTexts.Add("REF", mText.X + DecalRef.X, mText.Y + DecalRef.Y)
                    'TxtRef.AnchorPosition = catMiddleLeft + 20
                    'TxtRef.SetFontSize 0, 0, 4
                    'TxtRef.SetFontName 0, 0, "Times New Roman"
                    'AssociatText mText, TxtRef
                    Exit For
                Else
                    LabelRef = mText.Text
                End If
            Else
                LabelRef = mText.Text
            End If
        Next
    End If

End Function

Private Function LocateLbl(lbl As DrawingText, ech As Double, Angle As Double) As CoordXY
'Renvoi la position du label dans la vue multiplié par le facteur d'echelle de la vue
'Calcul le changement de repère pour les vues inclinées
Dim rAngle As Double
Dim AnchorBulle As CoordXY 'coordonées corrigés en fonction du point d'accrochage du texte

    AnchorBulle = AnchorLbl(lbl)

    If Sgn(Angle) < 0 Then
        Angle = Pi * 2 + Angle
    End If
    rAngle = Round(Angle, 10)
    If rAngle = 0 Then
        LocateLbl.X = lbl.X * ech
        LocateLbl.Y = lbl.Y * ech
    ElseIf rAngle > 0 And rAngle < Round(Pi / 2, 10) Then
        LocateLbl.X = (cos(rAngle) * lbl.X - Sin(rAngle) * lbl.Y) * ech
        LocateLbl.Y = (cos(rAngle) * lbl.X + Sin(rAngle) * lbl.Y) * ech
    ElseIf rAngle = Round(Pi / 2, 10) Then
        LocateLbl.X = -lbl.Y * ech
        LocateLbl.Y = lbl.X * ech
    ElseIf rAngle > Round(Pi / 2, 10) And rAngle < Round(Pi, 10) Then
        LocateLbl.X = -((cos(rAngle) * lbl.X - Sin(rAngle) * lbl.Y) * ech)
        LocateLbl.Y = (cos(rAngle) * lbl.X + Sin(rAngle) * lbl.Y) * ech
    ElseIf rAngle = Round(Pi, 10) Then
        LocateLbl.X = -lbl.X * ech
        LocateLbl.Y = -lbl.Y * ech
    ElseIf rAngle > Round(Pi, 10) And rAngle < Round(Pi + (Pi / 2), 10) Then
        LocateLbl.X = -((cos(rAngle) * lbl.X - Sin(rAngle) * lbl.Y) * ech)
        LocateLbl.Y = -((cos(rAngle) * lbl.X + Sin(rAngle) * lbl.Y) * ech)
    ElseIf rAngle = Round(Pi + (Pi / 2), 10) Then
        LocateLbl.X = lbl.Y * ech
        LocateLbl.Y = -lbl.X * ech
    ElseIf rAngle > Round(Pi + (Pi / 2), 10) And rAngle < Round(2 * Pi, 10) Then
        LocateLbl.X = (cos(rAngle) * lbl.X - Sin(rAngle) * lbl.Y) * ech
        LocateLbl.Y = -((cos(rAngle) * lbl.X + Sin(rAngle) * lbl.Y) * ech)
    Else
        MsgBox "Hola !"
    End If
End Function

Private Function AnchorLbl(lbl As DrawingText) As CoordXY
'corrige les coordonnées du point d'accrochage du label en fonctio du point d'ancrage
Dim AnchorPt As cattextanchorposition
Dim Rayon As Double

    AnchorPt = lbl.AnchorPosition - 20
    Rayon = RayBulle(lbl)
    ' Correction du X
    Select Case AnchorPt
        Case catTopLeft, catMiddleLeft, catBottomLeft
            AnchorLbl.X = AnchorLbl.X + 2 * Rayon
        Case catTopCenter, catMiddleCenter, catBottomCenter
            AnchorLbl.X = AnchorLbl.X + Rayon
        Case catTopRight, catMiddleRight, catBottomRight
            AnchorLbl.X = AnchorLbl.X
    End Select
     ' Correction du Y
    Select Case AnchorPt
        Case catTopLeft, catTopCenter, catTopRight
            AnchorLbl.Y = AnchorLbl.Y - Rayon
        Case catMiddleLeft, catMiddleCenter, catMiddleRight
        
        Case catBottomLeft, catBottomCenter, catBottomRight
            AnchorLbl.Y = AnchorLbl.Y + Rayon
    End Select
    
End Function

Private Function RayBulle(txt As DrawingText) As Double
'Calcule le rayon de la bulle d'un label en fonction du nombre de carractères
Dim nbCar As Integer

    nbCar = Len(txt.Text)
    Select Case nbCar
        Case 2
            RayBulle = (txt.TextProperties.FONTSIZE * nbCar * 1.2857) / 2 '1.372
        Case 3
            RayBulle = (txt.TextProperties.FONTSIZE * nbCar * 1.0666) / 2 ' 1.248
    End Select
End Function

Private Function PosLbl(lbl As DrawingText, Vue As DrawingView, oreglesH, oreglesV, DimCalque As CoordXY) As String
'Renvois les coordonnées A1-G9 d'un label en fonction de sa position dans la vue et de lapositin de la vue dans le calque
'En prenant en compte les lettres "interdites" (G,I,O,P,S,X,Y,Z)
'Lbl = Label
'Vue = drawingView
'DimCalque = dimension du calque

Dim CoordLbl As CoordXY 'Position du label dans la vue
Dim CoordVue As CoordXY 'Position de la vue dans le plan
Dim CoordPlan As CoordXY 'Position relative du label dans le plan
Dim NoCarreauH As String, NoCarreauV As String
Dim tRegle As c_Regle
    
    'initialisation des classes
    Set tRegle = New c_Regle

    'calcul de la position du label en fonction de l'échelle de la vue
    CoordLbl = LocateLbl(lbl, Vue.Scale, Vue.Angle)
    CoordVue.X = Vue.xAxisData
    CoordVue.Y = Vue.yAxisData
    
    CoordPlan.X = ArrondiVersInfinis(DimCalque.X - (CoordVue.X + CoordLbl.X))
    CoordPlan.Y = ArrondiVersInfinis(CoordVue.Y + CoordLbl.Y)
    'Recherche du carreau hrizontal
    For Each tRegle In oreglesH.Items
        If CoordPlan.X > tRegle.Limit Then
            NoCarreauH = tRegle.No
        End If
    Next
    'Recherche du carreau vertical
    For Each tRegle In oreglesV.Items
        If CoordPlan.Y > tRegle.Limit Then
            NoCarreauV = tRegle.No
        End If
    Next
    
    PosLbl = NoCarreauV & NoCarreauH
    
    'Libération des classes
    Set tRegle = Nothing

End Function


Private Sub exportXlLbl(collabs)
'Export le contenu de la collection vers un fichier excel pour verification
Dim oXl
Dim oWBK
Dim lig As Long
'Dim olab As c_Label
Dim olab As c_Label

    lig = 1
    Set oXl = CreateObject("EXCEL.APPLICATION")
    Set oWBK = oXl.Workbooks.Add
    oXl.Visible = True
    oWBK.ActiveSheet.cells(lig, "A").Value = "No"
    oWBK.ActiveSheet.cells(lig, "B").Value = "Rep"
    oWBK.ActiveSheet.cells(lig, "C").Value = "Position"
    oWBK.ActiveSheet.cells(lig, "D").Value = "Planche"
    oWBK.ActiveSheet.cells(lig, "E").Value = "Vue"

    For lig = 1 To collabs.Count
        Set olab = collabs.Item(lig)
        oWBK.ActiveSheet.cells(lig + 1, "A").Value = olab.No
        oWBK.ActiveSheet.cells(lig + 1, "B").Value = olab.Rep
        oWBK.ActiveSheet.cells(lig + 1, "C").Value = olab.Position
        oWBK.ActiveSheet.cells(lig + 1, "D").Value = olab.PL
        oWBK.ActiveSheet.cells(lig + 1, "E").Value = olab.RefView
    Next
    
'libération des classes
Set olab = Nothing
Set oXl = Nothing
Set oWBK = Nothing

End Sub

Private Sub AssociatText(TxtParent As DrawingText, TxtEnfant As DrawingText)
'Lie un texte à un autre
    TxtEnfant.AssociativeElement = TxtParent
End Sub

Public Function ArrondiVersInfinis(ByVal Nombre, Optional ByVal Decimales = 0)
' Fonction Arrondi vers les infinis : au chiffre supérieur
  ArrondiVersInfinis = (Fix(Nombre * 10 ^ Decimales) _
    + IIf(Nombre = Fix(Nombre * 10 ^ Decimales), 0, Sgn(Nombre))) / 10 ^ Decimales

End Function

Attribute VB_Name = "c_Attribut"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Attribut
'Classe des attributs personaliés sur les part et products
'l'ordre correspond à la colonne de l'attribut dans le fichier de nomenclature Catia
Private mvarNom As String
Private mvarOrdre As Integer
Private mvarValeur As String

Public Property Let Nom(ByVal vData As String)
    mvarNom = vData
End Property

Public Property Get Nom() As String
    Nom = mvarNom
End Property

Public Property Let Ordre(ByVal vData As Integer)
    mvarOrdre = vData
End Property

Public Property Get Ordre() As Integer
    Ordre = mvarOrdre
End Property

Public Property Let Valeur(ByVal vData As String)
    mvarValeur = vData
End Property

Public Property Get Valeur() As String
    Valeur = mvarValeur
End Property

Attribute VB_Name = "c_Attributs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Attributs
'Classe des attributs personaliés sur les part et products
'l'ordre correspond à la colonne de l'attribut dans le fichier de nomenclature Catia
'La classe ne devant pas contenir de doublon, elle est indexée
Private mcol As Collection

Public Function Add(Nom As String, _
            Optional Ordre As Integer = 100, _
            Optional Valeur As String = "") As c_Attribut
    
    Dim objNewMember As c_Attribut
    Set objNewMember = New c_Attribut
    
    objNewMember.Nom = Nom
    objNewMember.Ordre = Ordre
    objNewMember.Valeur = Valeur

    mcol.Add objNewMember, Nom

    Set Add = objNewMember
    Set objNewMember = Nothing

End Function

Public Property Get Item(vntIndexKey As Variant) As c_Attribut
  Set Item = mcol(vntIndexKey)
End Property

Public Property Get Count() As Long
    Count = mcol.Count
End Property

Public Property Get Items() As Collection
    Set Items = mcol
End Property

Public Sub Remove(vntIndexKey As Variant)
    mcol.Remove vntIndexKey
End Sub

Private Sub Class_initialize()
    Set mcol = New Collection
End Sub

Private Sub Class_Terminate()
    Set mcol = Nothing
End Sub

Attribute VB_Name = "c_CCode"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_CCode
'Cage Codes

Private mvarNo As String
Private mvarDom As String
Private mvarNom As String
Private mvarEU As Integer
Private mvarUS As String

Public Property Let No(ByVal vData As String)
    mvarNo = vData
End Property

Public Property Get No() As String
    No = mvarNo
End Property

Public Property Let Dom(ByVal vData As String)
    mvarDom = vData
End Property

Public Property Get Dom() As String
    Dom = mvarDom
End Property

Public Property Let Nom(ByVal vData As String)
    mvarNom = vData
End Property

Public Property Get Nom() As String
    Nom = mvarNom
End Property

Public Property Let EU(ByVal vData As Integer)
    mvarEU = vData
End Property

Public Property Get EU() As Integer
    EU = mvarEU
End Property

Public Property Let US(ByVal vData As String)
    mvarUS = vData
End Property

Public Property Get US() As String
    US = mvarUS
End Property

Attribute VB_Name = "c_CCodes"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c-CCodes
'Collection des cage Codes

Private mcol As Collection

Public Function Add(No As String, _
                    Optional Dom As String = "", _
                    Optional Nom As String = "", _
                    Optional EU As String = "", _
                    Optional US As String = "") As c_CCode
    
    Dim objNewMember As c_CCode
    Set objNewMember = New c_CCode
    
    objNewMember.No = No
    objNewMember.Dom = Dom
    objNewMember.Nom = Nom
    objNewMember.EU = EU
    objNewMember.US = US

    mcol.Add objNewMember, No

    Set Add = objNewMember
    Set objNewMember = Nothing

End Function

Public Property Get Items() As Collection
    Set Items = mcol
End Property

Public Property Get Item(vntIndexKey As Variant) As c_CCode
  Set Item = mcol(vntIndexKey)
End Property

Public Property Get Count() As Long
    Count = mcol.Count
End Property

Public Sub Remove(vntIndexKey As Variant)
    mcol.Remove vntIndexKey
End Sub

Private Sub Class_initialize()
    Set mcol = New Collection
End Sub

Private Sub Class_Terminate()
    Set mcol = Nothing
End Sub

Attribute VB_Name = "c_ItNomSnecma"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_ItNom
'Classe Item Nomenclature
Private mvarNo As String        'Index
Private mvarG03 As String       'Contenu de la colonne G03
Private mvarG02 As String       'Contenu de la colonne G02
Private mvarG01 As String       'Contenu de la colonne G01
Private mvarIdent As String     'Contenu de la colonne Identification
Private mvarCageCode As String  'Contenu de la colonne CageCode
Private mvarDet As String       'Contenu de la colonne Det/Sh/NO
Private mvarZone As String       'Contenu de la colonne ITEM/ZONE
Private mvarRep As String       'Contenu de la colonne ITEM/NO/Rep
Private mvarDesc As String       'Contenu de la colonne Description
Private mvarFourn As String      'Adresses des fournisseurs

Public Property Let No(ByVal vData As String)
    mvarNo = vData
End Property

Public Property Get No() As String
    No = mvarNo
End Property

Public Property Let G03(ByVal vData As String)
    mvarG03 = vData
End Property

Public Property Get G03() As String
    G03 = mvarG03
End Property

Public Property Let G02(ByVal vData As String)
    mvarG02 = vData
End Property

Public Property Get G02() As String
    G02 = mvarG02
End Property

Public Property Let G01(ByVal vData As String)
    mvarG01 = vData
End Property

Public Property Get G01() As String
    G01 = mvarG01
End Property

Public Property Let Ident(ByVal vData As String)
    mvarIdent = vData
End Property

Public Property Get Ident() As String
    Ident = mvarIdent
End Property

Public Property Let CageCode(ByVal vData As String)
    mvarCageCode = vData
End Property

Public Property Get CageCode() As String
    CageCode = mvarCageCode
End Property

Public Property Let Det(ByVal vData As String)
    mvarDet = vData
End Property

Public Property Get Det() As String
    Det = mvarDet
End Property

Public Property Let Zone(ByVal vData As String)
    mvarZone = vData
End Property

Public Property Get Zone() As String
    Zone = mvarZone
End Property

Public Property Let Rep(ByVal vData As String)
    mvarRep = vData
End Property

Public Property Get Rep() As String
    Rep = mvarRep
End Property

Public Property Let desc(ByVal vData As String)
    mvarDesc = vData
End Property

Public Property Get desc() As String
    desc = mvarDesc
End Property

Public Property Let Fourn(ByVal vData As String)
    mvarFourn = vData
End Property

Public Property Get Fourn() As String
    Fourn = mvarFourn
End Property

Attribute VB_Name = "c_ItNomSnecmas"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_ItNoms
'Collection des item de nomenclature
Private mcol As Collection

Public Function Add(No As String, _
                    Optional G03 As String = "", _
                    Optional G02 As String = "", _
                    Optional G01 As String = "", _
                    Optional Ident As String = "", _
                    Optional CageCode As String = "", _
                    Optional Det As String = "", _
                    Optional Zone As String = "", _
                    Optional Rep As String = "", _
                    Optional desc As String = "", _
                    Optional Fourn As String = "") As c_ItNomSnecma
    
    Dim objNewMember As c_ItNomSnecma
    Set objNewMember = New c_ItNomSnecma
    
    objNewMember.No = No
    objNewMember.G03 = G03
    objNewMember.G02 = G02
    objNewMember.G01 = G01
    objNewMember.Ident = Ident
    objNewMember.CageCode = CageCode
    objNewMember.Det = Det
    objNewMember.Zone = Zone
    objNewMember.Rep = Rep
    objNewMember.desc = desc
    objNewMember.Fourn = Fourn

    mcol.Add objNewMember, No

    Set Add = objNewMember
    Set objNewMember = Nothing

End Function

Public Property Get Items() As Collection
    Set Items = mcol
End Property

Public Property Get Item(vntIndexKey As Variant) As c_ItNomSnecma
  Set Item = mcol(vntIndexKey)
End Property

Public Property Get Count() As Long
    Count = mcol.Count
End Property

Public Sub Remove(vntIndexKey As Variant)
    mcol.Remove vntIndexKey
End Sub

Private Sub Class_initialize()
    Set mcol = New Collection
End Sub

Private Sub Class_Terminate()
    Set mcol = Nothing
End Sub

Attribute VB_Name = "c_LNomCatia"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_LNomCatia
'Collection des infos d'une ligne de nomenclature
'Les attributs Reference,Qte, Revsion, Definition, Nomenclature, Source et Description sont toujours présents dans les parts et Products
'Les attributs personalisés sont collectés dans la collection c_attributs

Private mvarRef As String            'Référence de l'objet (Part Number)
Private mvarComp As String           'Type de composant Ensemble("E") ou pièce("P")
Private mvarQte As Long              'Quantité de composant
Private mvarRev As String            'Revision
Private mvarDef As String            'Definition
Private mvarNom As String            'Nomenclature
Private mvarsource As String         'Source (Fabriqué ou Acheté)
Private mvarDesc As String           'Description du composant (description ref)
Private mvarAttributs As c_Attributs 'collection des attributs personalisés du composant
Private mvarParent As String         'Nom de l'ensemble parent

Public Property Let ref(ByVal vData As String)
    mvarRef = vData
End Property

Public Property Get ref() As String
    ref = mvarRef
End Property

Public Property Let Comp(ByVal vData As String)
    mvarComp = vData
End Property

Public Property Get Comp() As String
    Comp = mvarComp
End Property

Public Property Let Qte(ByVal vData As Long)
    mvarQte = vData
End Property

Public Property Get Qte() As Long
    Qte = mvarQte
End Property

Public Property Let Rev(ByVal vData As String)
    mvarRev = vData
End Property

Public Property Get Rev() As String
    Rev = mvarRev
End Property

Public Property Let Def(ByVal vData As String)
    mvarDef = vData
End Property

Public Property Get Def() As String
    Def = mvarDef
End Property

Public Property Let Nom(ByVal vData As String)
    mvarNom = vData
End Property

Public Property Get Nom() As String
    Nom = mvarNom
End Property

Public Property Let Source(ByVal vData As String)
    mvarsource = vData
End Property

Property Get Source() As String
    Source = mvarsource
End Property

Public Property Let desc(ByVal vData As String)
    mvarDesc = vData
End Property

Public Property Get desc() As String
    desc = mvarDesc
End Property

Public Property Let Attributs(ByVal oData As c_Attributs)
    Set mvarAttributs = oData
End Property

Public Property Get Attributs() As c_Attributs
    Set Attributs = mvarAttributs
End Property

Public Property Let Parent(ByVal vData As String)
    mvarParent = vData
End Property

Property Get Parent() As String
    Parent = mvarParent
End Property

Attribute VB_Name = "c_LNomCatias"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_LNomCatials
'Collection des lignes de nomenclature générées par Catia
'Ref, Qte, Rev, Def, Nom, Source et Desc sont de propriétés de base présentes sur tout les part et product
'Les autre propriétés sont collectées dans la classe "attributs"
'La classe ne devant pas contenir de doublon, elle est indexée
Private mcol As Collection

Public Function Add(ref As String, _
            Optional Comp As String = "", _
            Optional Qte As Long = 0, _
            Optional Rev As String = "", _
            Optional Def As String = "", _
            Optional Nom As String = "", _
            Optional Source As String = "", _
            Optional desc As String = "", _
            Optional Attributs As c_Attributs = Nothing, _
            Optional Parent As String) As c_LNomCatia
    
    Dim objNewMember As c_LNomCatia
    Set objNewMember = New c_LNomCatia
    
    objNewMember.ref = ref
    objNewMember.Comp = Comp
    objNewMember.Qte = Qte
    objNewMember.Rev = Rev
    objNewMember.Def = Def
    objNewMember.Nom = Nom
    objNewMember.Source = Source
    objNewMember.desc = desc
    objNewMember.Attributs = Attributs
    objNewMember.Parent = Parent

    mcol.Add objNewMember, ref

    Set Add = objNewMember
    Set objNewMember = Nothing

End Function

Public Property Get Item(vntIndexKey As Variant) As c_LNomCatia
  Set Item = mcol(vntIndexKey)
End Property

Public Property Get Count() As Long
    Count = mcol.Count
End Property

Public Property Get Items() As Collection
    Set Items = mcol
End Property

Public Sub Remove(vntIndexKey As Variant)
    mcol.Remove vntIndexKey
End Sub

Private Sub Class_initialize()
    Set mcol = New Collection
End Sub

Private Sub Class_Terminate()
    Set mcol = Nothing
End Sub

Attribute VB_Name = "c_Label"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Label

Private mvarNo As String
Private mvarRep As String
Private mvarPL As String
Private mvarPosition As String
Private mvarRefView As String

Public Property Let No(ByVal vData As String)
    mvarNo = vData
End Property

Public Property Get No() As String
    No = mvarNo
End Property

Public Property Let Rep(ByVal vData As String)
    mvarRep = vData
End Property

Public Property Get Rep() As String
    Rep = mvarRep
End Property

Public Property Let PL(ByVal vData As String)
    mvarPL = vData
End Property

Public Property Get PL() As String
    PL = mvarPL
End Property

Public Property Let Position(ByVal vData As String)
    mvarPosition = vData
End Property

Public Property Get Position() As String
    Position = mvarPosition
End Property

Public Property Let RefView(ByVal vData As String)
    mvarRefView = vData
End Property

Public Property Get RefView() As String
    RefView = mvarRefView
End Property

Attribute VB_Name = "c_Labels"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Labels
Private mcol As Collection

Public Function Add(No As String, _
                    Optional Rep As String = "", _
                    Optional PL As String = "", _
                    Optional Position As String = "", _
                    Optional RefView As String = "") As c_Label
    
    Dim objNewMember As c_Label
    Set objNewMember = New c_Label
    
    objNewMember.No = No
    objNewMember.Rep = Rep
    objNewMember.PL = PL
    objNewMember.Position = Position
    objNewMember.RefView = RefView

    mcol.Add objNewMember

    Set Add = objNewMember
    Set objNewMember = Nothing

End Function

Public Property Get Items() As Collection
    Set Items = mcol
End Property

Public Property Get Item(vntIndexKey As Variant) As c_Label
  Set Item = mcol(vntIndexKey)
End Property

Public Property Get Count() As Long
    Count = mcol.Count
End Property

Public Sub Remove(vntIndexKey As Variant)
    mcol.Remove vntIndexKey
End Sub

Private Sub Class_initialize()
    Set mcol = New Collection
End Sub

Private Sub Class_Terminate()
    Set mcol = Nothing
End Sub

Attribute VB_Name = "c_Lig_Nom"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Lig_Nom
'Classe des lignes de nomenclature Snecma CFMI std 121
'valable pour l'entète et pour les lignes de nom
'Les informations sont collectées dans un fichier texte
Private mvarNo As String        'Index
Private mvarNom As String       'Nom de l'oblet ligne dans Catia (ex Droite.50....)
Private mvarXd As Double         'Position en X du point de départ de la ligne
Private mvarYd As Double         'Position en Y du point de départ de la ligne
Private mvarXa As Double         'Position en X du point d'arrivee de la ligne
Private mvarYa As Double         'Position en Y du point d'arrivee de la ligne
Private mvarCoul As String        'Couleur de la ligne


Public Property Let No(ByVal vData As String)
    mvarNo = vData
End Property

Public Property Get No() As String
    No = mvarNo
End Property

Public Property Let Nom(ByVal vData As String)
    mvarNom = vData
End Property

Public Property Get Nom() As String
    Nom = mvarNom
End Property

Public Property Let Xd(ByVal vData As Double)
    mvarXd = vData
End Property

Public Property Get Xd() As Double
    Xd = mvarXd
End Property

Public Property Let Yd(ByVal vData As Double)
    mvarYd = vData
End Property

Public Property Get Yd() As Double
    Yd = mvarYd
End Property

Public Property Let Xa(ByVal vData As Double)
    mvarXa = vData
End Property

Public Property Get Xa() As Double
    Xa = mvarXa
End Property

Public Property Let Ya(ByVal vData As Double)
    mvarYa = vData
End Property

Public Property Get Ya() As Double
    Ya = mvarYa
End Property

Attribute VB_Name = "c_ProgressBarre"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'*********************************************************************
'* Classe : c_ProgressBarre
'*
'* Fonctions :  Afficher et faire défiler une barre de progression avec
'*              différentes informations
'*
'*
'* Version : 1
'* Création :  CFR
'* Modification : 15/04/17
'*                Ajout fonction de balayage
'*
'**********************************************************************

Private Sub Class_initialize()
    'affichage de la barre de progression
    Load Frm_Progression
    Frm_Progression.Show vbModeless

End Sub

Property Let Balayage(ValProgress As Long)
'Modifie la longueur et la position de la barre de progression
'Pour effectuer un balayage.
'Utilisé lorsque le traitement peu être long et qu'on ne peu pas calculer le nombre d'opérations
 Dim Lgbarre As Integer
 Dim posMin As Integer, posMax As Integer, DebBarre As Integer, FinBarre As Integer
 
    Lgbarre = 7
    posMin = 18
    posMax = 318
    While ValProgress > 100
        ValProgress = ValProgress - 100
    Wend
    If ValProgress < Lgbarre Then
        DebBarre = posMin
        FinBarre = ValProgress * 3
    ElseIf (ValProgress >= 100 - Lgbarre And ValProgress < 100) Then
        DebBarre = ValProgress * 3
        'FinBarre = (Lgbarre * 3 - (posMax - posMin - ValProgress * 3)) * 3
        FinBarre = (posMax - posMin - ValProgress * 3)
    ElseIf ValProgress >= Lgbarre And ValProgress < 100 - Lgbarre Then
        DebBarre = ValProgress * 3
        FinBarre = Lgbarre * 3
    End If
    
        Frm_Progression.Bar1.Left = DebBarre
        Frm_Progression.Bar1.Width = FinBarre

    
       
End Property

Property Let Progression(ValProgress As Long)
'Modifie la longueur de la barre de progression
    If ValProgress > 100 Then PBAvancement = 100
    If ValProgress < 1 Then ValProgress = 1
    Frm_Progression.Bar1.Width = ValProgress * 3

End Property

Property Let Titre(StrTitre As String)
'Change le texte de titre du formulaire
    Frm_Progression.Caption = StrTitre
End Property

Property Let Etape(StrEtape As String)
'Change le texte dans la barre de progression
    Frm_Progression.Lbl_Etape = StrEtape
End Property

Public Sub ProgressTitre(ValProgess As Long, StrTitre As String)
' Modifie la longueur de la barre de progression et change le titre en une seule fonction
    Titre = StrTitre
    Progression = ValProgess
End Sub

Public Sub ProgressEtape(ValProgess As Long, StrEtape As String)
' Modifie la longueur de la barre de progression et change le texte dans la barre de progression en une seule fonction
    Etape = StrEtape
    Progression = ValProgess
End Sub

Public Sub CalculProgression(PB_Etape As Long, PB_Nb_Etapes As Long, PB_Item As Long, PB_NbItem As Long, PB_Caption As String)
'gestion de l'avancement de la barre de progression pour une succession d'étapes contenant plusieurs item

' PB_Etape = etape en cours
' PB_Nb_Etapes = nombre d'étapes
' PB_Item = item en cours de l'étape en cours
' PB_NbItem = Nombre d'items dans l'étape en cour
' PB_Caption = Titre de la fenètre
'(((PB_Etape - 1) * (100 / PB_NB_Etapes)) + (((100 / PB_NB_Etapes) / PB_NbItem) * PB_Item))
Dim PB_Barre As Long
    Titre = PB_Caption
    If PB_Nb_Etapes = 0 Or PB_NbItem = 0 Then
        Exit Sub
    End If
    PB_Barre = (((PB_Etape - 1) * (100 / PB_Nb_Etapes)) + (((100 / PB_Nb_Etapes) / PB_NbItem) * PB_Item))
    Progression = PB_Barre
End Sub

Public Sub Cache()
'Masque la barre de progression
    Frm_Progression.Hide
End Sub

Public Sub Affiche()
'Affiche la barre de progression
    Frm_Progression.Show vbModeless
End Sub

Private Sub Class_Terminate()
'masque et décharge de la barre de progression
    Frm_Progression.Hide
    Unload Frm_Progression
    
End Sub

Attribute VB_Name = "c_Regle"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Regle
'Classe des carreaux horizontaux ou verticaux
'permattant de localiser les objets dans le plan
Private mvarNo As String
Private mvarLimit As Double

Public Property Let No(ByVal vData As String)
    mvarNo = vData
End Property

Public Property Get No() As String
    No = mvarNo
End Property

Public Property Let Limit(ByVal vData As Double)
    mvarLimit = vData
End Property

Public Property Get Limit() As Double
    Limit = mvarLimit
End Property

Attribute VB_Name = "c_Regles"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Regles
Private mcol As Collection

Public Function Add(No As String, Limit As Double) As c_Regle
    
    Dim objNewMember As c_Regle
    Set objNewMember = New c_Regle
    
    objNewMember.No = No
    objNewMember.Limit = Limit

    mcol.Add objNewMember

    Set Add = objNewMember
    Set objNewMember = Nothing

End Function

Public Property Get Items() As Collection
    Set Items = mcol
End Property

Public Property Get Item(vntIndexKey As Variant) As c_Regle
  Set Item = mcol(vntIndexKey)
End Property

Public Property Get Count() As Long
    Count = mcol.Count
End Property

Public Sub Remove(vntIndexKey As Variant)
    mcol.Remove vntIndexKey
End Sub

Private Sub Class_initialize()
    Set mcol = New Collection
End Sub

Private Sub Class_Terminate()
    Set mcol = Nothing
End Sub

Attribute VB_Name = "c_Sheet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Sheet

Private mvarNom As String
Private mvarOrdre As Integer
Private mvarValeur As String

Public Property Let Nom(ByVal vData As String)
    mvarNom = vData
End Property

Public Property Get Nom() As String
    Nom = mvarNom
End Property

Public Property Let Ordre(ByVal vData As Integer)
    mvarOrdre = vData
End Property

Public Property Get Ordre() As Integer
    Ordre = mvarOrdre
End Property

Public Property Let Valeur(ByVal vData As String)
    mvarValeur = vData
End Property

Public Property Get Valeur() As String
    Valeur = mvarValeur
End Property

Attribute VB_Name = "c_Txt_Nom"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Txt_Nom
'Classe des texte de l'entète de nomenclature Snecma CFMI std 121
'Les informations sont collectées dans un fichier texte
Private mvarNo As String        'Index
Private mvarNom As String       'Nom de l'oblet texte dans Catia (ex TABLIG1_COL....)
Private mvarTexte As String     'Contenu du texte
Private mvarPolice As String    'Police du texte
Private mvarTaille As String    'Taille du text
Private mvarCoul As Long        'Couleur du texte
Private mvarX As Double         'Position en X du texte
Private mvarY As Double         'Position en Y du texte

Public Property Let No(ByVal vData As String)
    mvarNo = vData
End Property

Public Property Get No() As String
    No = mvarNo
End Property

Public Property Let Nom(ByVal vData As String)
    mvarNom = vData
End Property

Public Property Get Nom() As String
    Nom = mvarNom
End Property

Public Property Let Texte(ByVal vData As String)
    mvarTexte = vData
End Property

Public Property Get Texte() As String
    Texte = mvarTexte
End Property

Public Property Let Police(ByVal vData As String)
    mvarPolice = vData
End Property

Public Property Get Police() As String
    Police = mvarPolice
End Property

Public Property Let Coul(ByVal vData As Long)
    mvarCoul = vData
End Property

Public Property Get Coul() As Long
    Coul = mvarCoul
End Property

Public Property Let X(ByVal vData As Double)
    mvarX = vData
End Property

Public Property Get X() As Double
    X = mvarX
End Property

Public Property Let Y(ByVal vData As Double)
    mvarY = vData
End Property

Public Property Get Y() As Double
    Y = mvarY
End Property

Attribute VB_Name = "c_Txt_Noms"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Txt_Noms
Private mcol As Collection

Public Function Add(No As String, _
                    Optional Nom As String = "", _
                    Optional Texte As String = "", _
                    Optional Police As String = "", _
                    Optional Coul As Long = 0, _
                    Optional X As Double = 0, _
                    Optional Y As Double = 0) As c_Txt_Nom
    
    Dim objNewMember As c_Txt_Nom
    Set objNewMember = New c_Txt_Nom
    
    objNewMember.No = No
    objNewMember.Nom = Nom
    objNewMember.Texte = Texte
    objNewMember.Police = Police
    objNewMember.Coul = Coul
    objNewMember.X = X
    objNewMember.Y = Y

    mcol.Add objNewMember, No

    Set Add = objNewMember
    Set objNewMember = Nothing

End Function

Public Property Get Items() As Collection
    Set Items = mcol
End Property

Public Property Get Item(vntIndexKey As Variant) As c_Txt_Nom
  Set Item = mcol(vntIndexKey)
End Property

Public Property Get Count() As Long
    Count = mcol.Count
End Property

Public Sub Remove(vntIndexKey As Variant)
    mcol.Remove vntIndexKey
End Sub

Private Sub Class_initialize()
    Set mcol = New Collection
End Sub

Private Sub Class_Terminate()
    Set mcol = Nothing
End Sub

Attribute VB_Name = "c_View"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_View

Private mvarNom As String
Private mvarEchelle As Double
Private mvarPosition As String
Private mvarRefView As DrawingView

Public Property Let Nom(ByVal vData As String)
    mvarNom = vData
End Property

Public Property Get Nom() As String
    Nom = mvarNom
End Property

Public Property Let echelle(ByVal vData As Double)
    mvarEchelle = vData
End Property

Public Property Get echelle() As Double
    echelle = mvarEchelle
End Property

Public Property Let Position(ByVal vData As String)
    mvarPosition = vData
End Property

Public Property Get Position() As String
    Position = mvarPosition
End Property

Public Property Let RefView(ByVal vData As DrawingView)
    mvarRefView = vData
End Property

Public Property Get RefView() As DrawingView
    RefView = mvarRefView
End Property
